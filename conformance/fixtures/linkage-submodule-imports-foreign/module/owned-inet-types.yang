module owned-inet-types {
  yang-version 1.1;
  namespace "urn:linkage-submodule-imports-foreign-inet";
  prefix inet;
  revision 2026-06-15;

  typedef ip-address {
    type string {
      pattern '[0-9]{1,3}\.[0-9]{1,3}\.[0-9]{1,3}\.[0-9]{1,3}';
    }
  }
}
