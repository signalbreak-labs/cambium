module reject-mandatory-leaf-missing {
  yang-version 1.1;
  namespace "urn:reject-mandatory-leaf-missing";
  prefix rmlm;
  revision 2026-09-27;

  container user {
    leaf name {
      type string;
      mandatory true;
    }
    leaf full-name { type string; }
  }
}
