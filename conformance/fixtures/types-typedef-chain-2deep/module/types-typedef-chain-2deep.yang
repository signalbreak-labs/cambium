module types-typedef-chain-2deep {
  namespace "urn:types-typedef-chain-2deep";
  prefix typestypedefchain2deep;

  yang-version 1;
  revision 2026-06-14;

  typedef base-ip {
    type string { pattern '[0-9]+\.[0-9]+\.[0-9]+\.[0-9]+'; }
  }
  typedef gateway-ip { type base-ip; }
  leaf gw { type gateway-ip; }
}
