module schema-identity-derived {
  namespace "urn:cambium:schema-identity-derived";
  prefix sid;
  yang-version 1.1;

  import schema-identity-base { prefix base; }

  identity mid {
    base base:base;
  }

  identity leaf {
    base mid;
  }
}
