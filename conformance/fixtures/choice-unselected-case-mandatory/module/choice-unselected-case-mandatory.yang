module choice-unselected-case-mandatory {
  yang-version 1.1;
  namespace "urn:choice-unselected-case-mandatory";
  prefix cucm;
  revision 2026-09-27;

  container tunnel {
    choice mode {
      case gre {
        leaf remote {
          type string;
          mandatory true;
        }
      }
      case mpls {
        leaf label { type uint32; }
      }
    }
  }
}
