module json-ietf-anydata-anyxml-representation {
  yang-version 1.1;
  namespace "urn:json-ietf-anydata-anyxml-representation";
  prefix jiaar;
  revision 2026-06-15;

  container top {
    container config {
      anydata metadata;
    }
    container payload {
      anyxml data;
    }
  }
}
