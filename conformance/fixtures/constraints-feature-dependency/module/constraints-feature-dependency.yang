module constraints-feature-dependency {
  yang-version 1.1;
  namespace "urn:constraints-feature-dependency";
  prefix cfd;
  revision 2026-06-14;

  feature a;
  feature b {
    if-feature a;
  }
  container top {
    leaf gated {
      if-feature "not b";
      type string;
    }
  }
}
