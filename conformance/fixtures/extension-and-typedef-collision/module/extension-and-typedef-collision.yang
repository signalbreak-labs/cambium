module extension-and-typedef-collision {
  yang-version 1.1;
  namespace "urn:extension-and-typedef-collision";
  prefix eatc;

  import ext-mod {
    prefix ext;
  }

  revision 2026-06-15;

  typedef Metadata {
    type string {
      length "1..255";
    }
  }

  container top {
    ext:Metadata "version";
    leaf meta { type Metadata; }
  }
}
