module leaflist-with-defaults {
  yang-version 1.1;
  namespace "urn:leaflist-with-defaults";
  prefix lwd;
  revision 2026-06-15;

  container top {
    leaf-list servers {
      type string;
      default "8.8.8.8";
      default "8.8.4.4";
    }
  }
}
