module schema-vendor-nokia-sros {
  yang-version 1.1;
  namespace "urn:cambium:schema-vendor-nokia-sros";
  prefix svns;

  include schema-vendor-nokia-system;
  include schema-vendor-nokia-service;
  include schema-vendor-nokia-policy;

  container configure {
    leaf commit-comment {
      type string;
    }
  }
}
