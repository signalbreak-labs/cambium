module linkage-import-prefix-base {
  yang-version 1.1;
  namespace "urn:linkage-import-prefix-base";
  prefix lipb;
  revision 2026-06-15;

  typedef port-number {
    type uint16 {
      range "1..65535";
    }
  }
}
