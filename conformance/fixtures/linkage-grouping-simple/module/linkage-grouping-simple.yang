module linkage-grouping-simple {
  yang-version 1.1;
  namespace "urn:linkage-grouping-simple";
  prefix lgs;
  revision 2026-06-15;

  grouping addr {
    leaf ip {
      type string;
    }
    leaf mask {
      type uint8;
    }
  }

  container intf {
    leaf name {
      type string;
    }
    uses addr;
    leaf mtu {
      type uint16;
    }
  }
}
