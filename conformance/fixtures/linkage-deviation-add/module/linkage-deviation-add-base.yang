module linkage-deviation-add-base {
  yang-version 1.1;
  namespace "urn:linkage-deviation-add-base";
  prefix ldab;
  revision 2026-06-15;

  container c {
    leaf optional-name {
      type string;
    }
  }
}
