module augment-cross-module-ident-collision-base {
  yang-version 1.1;
  namespace "urn:augment-cross-module-ident-collision-base";
  prefix acmib;
  revision 2026-06-15;

  container top {
    container config {
      leaf v {
        type string;
      }
    }
    leaf status {
      type string;
    }
  }
}
