module linkage-submodule-multi {
  yang-version 1.1;
  namespace "urn:linkage-submodule-multi";
  prefix lsmm;

  include linkage-submodule-multi-types;
  include linkage-submodule-multi-state;

  revision 2026-06-15;

  container device {
    uses device-state;
  }
}
