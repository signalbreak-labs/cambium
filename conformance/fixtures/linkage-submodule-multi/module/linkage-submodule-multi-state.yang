submodule linkage-submodule-multi-state {
  yang-version 1.1;
  belongs-to linkage-submodule-multi {
    prefix lsmm;
  }

  include linkage-submodule-multi-types;

  revision 2026-06-15;

  grouping device-state {
    leaf id {
      type device-id;
    }
    leaf online {
      type boolean;
    }
  }
}
