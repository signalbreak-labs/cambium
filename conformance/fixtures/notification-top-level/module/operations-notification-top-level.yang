module operations-notification-top-level {
  yang-version 1.1;
  namespace "urn:operations-notification-top-level";
  prefix orontl;
  revision 2026-06-15;

  notification link-state-change {
    leaf timestamp {
      type string;
    }
    leaf interface-name {
      type string;
    }
    leaf link-state {
      type enumeration {
        enum up;
        enum down;
      }
    }
    leaf reason {
      type string;
    }
  }
}
