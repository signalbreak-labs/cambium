module types-union-leafref-member {
  namespace "urn:types-union-leafref-member";
  prefix typesunionleafrefmember;

  yang-version 1.1;
  revision 2026-06-14;

  list interface {
    key name;
    leaf name { type string; }
  }
  leaf primary-or-static {
    type union {
      type leafref { path "/interface/name"; }
      type string { pattern '192\.168\.[0-9]+\.[0-9]+'; }
    }
  }
}
