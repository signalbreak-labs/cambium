module json-ietf-scalar-quoting-int-spans {
  namespace "urn:json-ietf-scalar-quoting-int-spans";
  prefix jisqis;
  revision 2026-06-15;

  container top {
    leaf i8 { type int8; }
    leaf i16 { type int16; }
    leaf i32 { type int32; }
    leaf i64 { type int64; }
    leaf u8 { type uint8; }
    leaf u16 { type uint16; }
    leaf u32 { type uint32; }
    leaf u64 { type uint64; }
  }
}
