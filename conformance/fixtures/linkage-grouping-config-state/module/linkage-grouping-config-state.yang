module linkage-grouping-config-state {
  yang-version 1.1;
  namespace "urn:linkage-grouping-config-state";
  prefix lgcs;
  revision 2026-06-15;

  grouping addr-params {
    leaf ip {
      type string;
    }
    leaf mask {
      type uint8;
    }
  }

  container intf {
    leaf name {
      type string;
    }
    container config {
      uses addr-params;
    }
    container state {
      config false;
      uses addr-params;
    }
  }
}
