module linkage-deviation-replace-type-base {
  yang-version 1.1;
  namespace "urn:linkage-deviation-replace-type-base";
  prefix ldrb;
  revision 2026-06-15;

  container c {
    leaf count {
      type uint64;
    }
  }
}
