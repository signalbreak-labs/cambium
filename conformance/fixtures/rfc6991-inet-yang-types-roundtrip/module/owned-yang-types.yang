module owned-yang-types {
  yang-version 1.1;
  namespace "urn:cambium:owned-yang-types";
  prefix oyng;
  revision 2026-06-15 {
    description "Owned minimal subset of RFC 6991 ietf-yang-types.";
  }

  typedef mac-address {
    type string {
      pattern '[0-9a-fA-F]{2}(:[0-9a-fA-F]{2}){5}';
    }
  }

  typedef date-and-time {
    type string {
      pattern '\d{4}-\d{2}-\d{2}T\d{2}:\d{2}:\d{2}(Z|[+-]\d{2}:\d{2})';
    }
  }

  typedef counter64 {
    type uint64;
  }
}
