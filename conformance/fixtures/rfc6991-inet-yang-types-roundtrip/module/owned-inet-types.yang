module owned-inet-types {
  yang-version 1.1;
  namespace "urn:cambium:owned-inet-types";
  prefix oinet;
  revision 2026-06-15 {
    description "Owned minimal subset of RFC 6991 ietf-inet-types.";
  }

  typedef ipv4-address {
    type string {
      pattern '[0-9]{1,3}\.[0-9]{1,3}\.[0-9]{1,3}\.[0-9]{1,3}';
    }
  }

  typedef ipv6-address {
    type string {
      pattern '[0-9a-fA-F:]+';
    }
  }

  typedef ip-address {
    type union {
      type ipv4-address;
      type ipv6-address;
    }
  }

  typedef ipv6-prefix {
    type string {
      pattern '[0-9a-fA-F:]+/[0-9]+';
    }
  }
}
