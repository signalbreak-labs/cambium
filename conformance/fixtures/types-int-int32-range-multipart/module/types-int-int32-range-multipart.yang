module types-int-int32-range-multipart {
  namespace "urn:types-int-int32-range-multipart";
  prefix typesintint32rangemultipart;

  yang-version 1;
  revision 2026-06-14;

  leaf priority { type int32 { range "-100..-1 | 1..100"; } }
}
