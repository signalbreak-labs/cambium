module constraints-default-types {
  yang-version 1.1;
  namespace "urn:constraints-default-types";
  prefix cdt;
  revision 2026-06-14;

  leaf hostname { type string; default "localhost"; }
  leaf port { type uint16; default 8080; }
  leaf enabled { type boolean; default true; }
  leaf-list nameserver { type string; default "8.8.8.8"; default "8.8.4.4"; }
  choice log-backend {
    default syslog;
    case syslog {
      leaf facility { type string; default "local0"; }
    }
    case file {
      leaf path { type string; }
    }
    case remote {
      leaf server { type string; }
    }
  }
}
