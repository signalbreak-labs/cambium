module reject-pattern-violation {
  yang-version 1.1;
  namespace "urn:reject-pattern-violation";
  prefix rpv;
  revision 2026-09-27;

  leaf hostname {
    type string {
      pattern '[a-z][a-z0-9-]*';
    }
  }
}
