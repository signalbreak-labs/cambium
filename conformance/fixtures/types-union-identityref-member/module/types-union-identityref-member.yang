module types-union-identityref-member {
  namespace "urn:types-union-identityref-member";
  prefix typesunionidentityrefmember;

  yang-version 1;
  revision 2026-06-14;

  identity protocol-base;
  identity tcp { base protocol-base; }
  identity udp { base protocol-base; }
  leaf transport {
    type union {
      type identityref { base protocol-base; }
      type uint16 { range "1..65535"; }
    }
  }
}
