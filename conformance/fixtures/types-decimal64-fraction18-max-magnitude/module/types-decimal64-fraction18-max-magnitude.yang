module types-decimal64-fraction18-max-magnitude {
  namespace "urn:types-decimal64-fraction18-max-magnitude";
  prefix typesdecimal64fraction18maxmagnitude;

  yang-version 1;
  revision 2026-06-14;

  leaf precise { type decimal64 { fraction-digits 18; range "0..9.223372036854775807"; } }
}
