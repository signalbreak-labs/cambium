module types-leafref-require-instance-false {
  namespace "urn:types-leafref-require-instance-false";
  prefix typesleafrefrequireinstancefalse;

  yang-version 1.1;
  revision 2026-06-14;

  list item {
    key id;
    leaf id { type string; }
  }
  leaf future-target { type leafref { path "/item/id"; require-instance false; } }
}
