module datatree-augment-derived-from-prefix {
  yang-version 1.1;
  namespace "urn:datatree-augment-derived-from-prefix";
  prefix aug;

  import datatree-augment-derived-from-prefix-base {
    prefix base;
  }

  identity aug-kind {
    base base:base-kind;
  }

  identity aug-child {
    base aug-kind;
  }

  augment "/base:top" {
    leaf guarded {
      must "derived-from(../base:kind, 'aug:aug-kind')";
      type string;
    }
  }
}
