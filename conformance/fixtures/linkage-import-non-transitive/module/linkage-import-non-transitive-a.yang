module linkage-import-non-transitive-a {
  yang-version 1.1;
  namespace "urn:linkage-import-non-transitive-a";
  prefix linta;

  import linkage-import-non-transitive-b {
    prefix lintb;
  }

  revision 2026-06-15;

  leaf bad {
    type c:color;
  }
}
