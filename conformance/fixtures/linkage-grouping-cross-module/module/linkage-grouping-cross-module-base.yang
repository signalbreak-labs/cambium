module linkage-grouping-cross-module-base {
  yang-version 1.1;
  namespace "urn:linkage-grouping-cross-module-base";
  prefix lgcb;
  revision 2026-06-15;

  grouping shared-addr {
    leaf ip {
      type string;
    }
    leaf mask {
      type uint8;
    }
  }
}
