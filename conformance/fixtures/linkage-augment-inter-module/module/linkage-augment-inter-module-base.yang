module linkage-augment-inter-module-base {
  yang-version 1.1;
  namespace "urn:linkage-augment-inter-module-base";
  prefix liaim-b;
  revision 2026-06-15;

  container interfaces {
    list interface {
      key "name";
      leaf name {
        type string;
      }
      leaf type {
        type string;
      }
    }
  }
}
