module linkage-augment-inter-module {
  yang-version 1.1;
  namespace "urn:linkage-augment-inter-module";
  prefix liaim;

  import linkage-augment-inter-module-base {
    prefix liaim-b;
  }

  revision 2026-06-15;

  augment "/liaim-b:interfaces/liaim-b:interface" {
    leaf speed {
      type uint32;
    }
  }
}
